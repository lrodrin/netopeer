module bluespace_node {
  yang-version 1;
  namespace "urn:cttc:params:xml:ns:yang:bluespace_node";
  prefix bluespace_node;

  organization
    "CTTC";
  contact
    "Laura Rodriguez <laura.rodriguez@cttc.es>";
  description
    "YANG version of the bluespace_node.";

  revision 2018-02-06 {
    description
      "Bluespace_node module in progress.";
  }

  grouping signal {
    leaf signal-id {
      type string;
    }

    leaf wavelength {
      type uint8;
    }

    leaf mode {
      type uint8;
    }

    leaf core {
        type string;
    }
  }

  grouping port {
    leaf port-id {
      type string;
    }

    list signal {
      key "signal-id";
      uses signal;
    }
  }

  grouping component {
    leaf component-id {
        type string;
    }

    container analog-rof {
        leaf param1 {
            type string;
        }
    }

    container digital-rof {
        leaf param2 {
            type string;
        }
    }

    container optical-beam-forming {
        leaf param3 {
            type string;
        }
    }

    container ethernet {
        leaf param4 {
            type string;
        }
    }

    grouping wdm {
        leaf wdm-id {
            type string;
        }

        list port {
          key "port-id";
          uses port;
        }
    }

    list sdm-wdm {
        key "wdm-id";
        uses wdm;
    }
  }

  container bluespace-node {
    leaf bluespace-node-id {
      type string;
    }

    leaf location {
        type string;
    }

    list components {
      key "component-id";
      uses component;
    }
  }
}
