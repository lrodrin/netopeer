module hello {
  yang-version 1;
  namespace "urn:opendaylight:params:xml:ns:yang:hello";
  prefix hello;

  revision 2015-02-24 {
    description
      "Basic Hello World YANG model.";
  }

  rpc hello-world {
    input {
      leaf name {
        type string;
      }
    }

    output {
      leaf greeting {
        type string;
      }
    }
  }
}
